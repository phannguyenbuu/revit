(vl-load-com)
(load "D:/Dropbox/_Documents/RevitAI/cad_scan_titleblocks.lsp")
(defun c:DoScan ( / )
  (setq f (open "D:/Dropbox/_Documents/RevitAI/scratch_tb_scan_1792195958398.txt" "w"))
  (setq ss nil)
  (setq ss (ssget "_I")) (if (not ss) (setq ss (ssget "_P")))
  (if (not ss)
    (setq ss (ssget "X" '((0 . "INSERT") (2 . "`*U*"))))
  )
  (if ss
    (repeat (setq i (sslength ss))
      (setq ent (ssname ss (setq i (1- i))))
      (setq ed (entget ent))
      (setq bn (cdr (assoc 2 ed)))
      (if (and bn (wcmatch (strcase bn) "`*U*"))
        (progn
          (setq btrEnt (tblobjname "BLOCK" bn))
          (if btrEnt
            (progn
              (setq btrNext (entnext btrEnt))
              (setq cellOffsets nil cellNames nil)
              (while btrNext
                (setq subEd (entget btrNext))
                (if (equal (cdr (assoc 0 subEd)) "INSERT")
                  (progn
                    (setq cellOffsets (cons (cdr (assoc 10 subEd)) cellOffsets))
                    (setq cellNames (cons (cdr (assoc 2 subEd)) cellNames))
                  )
                )
                (setq btrNext (entnext btrNext))
              )
              (if (> (length cellOffsets) 1)
                (progn
                  (setq cellOffsets (reverse cellOffsets))
                  (setq cellNames (reverse cellNames))
                  (setq firstCellName (car cellNames))
                  (setq tbBlockName "")
                  (setq tbRelOffset '(0.0 0.0 0.0))
                  (setq btrCell (tblobjname "BLOCK" firstCellName))
                  (if btrCell
                    (progn
                      (setq subSub (entnext btrCell))
                      (while subSub
                        (setq ssEd (entget subSub))
                        (if (equal (cdr (assoc 0 ssEd)) "INSERT")
                          (progn
                            (setq tbBlockName (cdr (assoc 2 ssEd)))
                            (setq tbRelOffset (cdr (assoc 10 ssEd)))
                          )
                        )
                        (setq subSub (entnext subSub))
                      )
                    )
                  )
                  (setq arrPos (cdr (assoc 10 ed)))
                  (setq arrBaseX (car arrPos))
                  (setq arrBaseY (cadr arrPos))
                  (setq tbW 42957.9)
                  (setq tbH 27533.7)
                  (setq k 0)
                  (foreach cOff cellOffsets
                    (setq cellBaseX (+ arrBaseX (car cOff) (car tbRelOffset)))
                    (setq cellBaseY (+ arrBaseY (cadr cOff) (cadr tbRelOffset)))
                    (setq xmin cellBaseX)
                    (setq ymin cellBaseY)
                    (setq xmax (+ xmin tbW))
                    (setq ymax (+ ymin tbH))
                    (setq p1 (list (+ xmin 100.0) (+ ymin 100.0) 0.0))
                    (setq p2 (list (- xmax 100.0) (- ymax 100.0) 0.0))
                    (setq ssInside (ssget "C" p1 p2))
                    (setq totalEnts 0 textCnt 0 dimCnt 0 lineCnt 0 hatchCnt 0)
                    (setq txtList nil)
                    (if ssInside
                      (repeat (setq n (sslength ssInside))
                        (setq entInside (ssname ssInside (setq n (1- n))))
                        (setq edInside (entget entInside))
                        (setq etInside (cdr (assoc 0 edInside)))
                        (setq bnInside (cdr (assoc 2 edInside)))
                        (if (not (equal bnInside bn))
                          (progn
                            (setq totalEnts (1+ totalEnts))
                            (if (or (equal etInside "TEXT") (equal etInside "MTEXT"))
                              (progn
                                (setq textCnt (1+ textCnt))
                                (setq txtList (cons (cdr (assoc 1 edInside)) txtList))
                              )
                            )
                            (if (equal etInside "DIMENSION") (setq dimCnt (1+ dimCnt)))
                            (if (or (equal etInside "LINE") (equal etInside "LWPOLYLINE")) (setq lineCnt (1+ lineCnt)))
                            (if (equal etInside "HATCH") (setq hatchCnt (1+ hatchCnt)))
                          )
                        )
                      )
                    )
                    (setq bestTitle "")
                    (foreach tStr (reverse txtList)
                      (if (or (wcmatch (strcase tStr) "*MB*")
                              (wcmatch (strcase tStr) "*B*N V*")
                              (wcmatch (strcase tStr) "*KH*I NH*")
                              (wcmatch (strcase tStr) "*CHI TI*T*")
                              (wcmatch (strcase tStr) "*S* *")
                              (wcmatch (strcase tStr) "*HI*N TR*NG*")
                              (wcmatch (strcase tStr) "*TR*C*"))
                        (if (equal bestTitle "")
                          (setq bestTitle tStr)
                        )
                      )
                    )
                    (if (and (equal bestTitle "") (> (length txtList) 0))
                      (setq bestTitle (car (reverse txtList)))
                    )
                    (write-line (strcat "ROW	" bn "	" (itoa k) "	" (if tbBlockName tbBlockName "") "	"
                                        (rtos xmin 2 2) "	" (rtos ymin 2 2) "	"
                                        (rtos xmax 2 2) "	" (rtos ymax 2 2) "	"
                                        (rtos tbW 2 2) "	" (rtos tbH 2 2) "	"
                                        (itoa totalEnts) "	" (itoa textCnt) "	"
                                        (itoa dimCnt) "	" (itoa lineCnt) "	" (itoa hatchCnt) "	"
                                        bestTitle) f)
                    (foreach tSample (reverse txtList)
                      (write-line (strcat "TXT	" (itoa k) "	" tSample) f)
                    )
                    (setq k (1+ k))
                  )
                )
              )
            )
          )
        )
      )
    )
  )
  (close f)
  (princ "
Done DoScan
")
  (princ)
)
(c:DoScan)
