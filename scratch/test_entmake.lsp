(progn
  (regapp "REVITAI_LEADER")
  (setq res1 (entmake (list '(0 . "LINE")
                            '(8 . "P-PIPE")
                            '(10 0.0 0.0 0.0)
                            '(11 100.0 100.0 0.0)
                            (list -3 '("REVITAI_LEADER" (1000 . "PIPE_LEADER"))))))
  (setq res2 (entmake (list '(0 . "LINE")
                            '(8 . "P-PIPE")
                            '(10 100.0 100.0 0.0)
                            '(11 200.0 200.0 0.0))))
  (setq ss1 (ssget "X" '((0 . "LINE") (-3 ("REVITAI_LEADER")))))
  (setq f (open "d:/Dropbox/_Documents/RevitAI/scratch_entmake_test.txt" "w"))
  (write-line (strcat "res1=" (vl-prin1-to-string res1)) f)
  (write-line (strcat "res2=" (vl-prin1-to-string res2)) f)
  (write-line (strcat "ss1=" (vl-prin1-to-string ss1)) f)
  (close f)
  (princ)
)
