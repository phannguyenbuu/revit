(progn
  (setq pt '(-95697.0 -1387305.9))
  (vla-ZoomCenter (vlax-get-acad-object) (vlax-3d-point pt) 4000)
  (setq ss (ssget "C" (list (- (car pt) 2500) (- (cadr pt) 2500)) (list (+ (car pt) 2500) (+ (cadr pt) 2500)) '((0 . "*TEXT,DIMENSION"))))
  (setq f (open "D:/Dropbox/_Documents/RevitAI/scratch/corner_texts.txt" "w"))
  (if ss
    (repeat (setq i (sslength ss))
      (setq e (ssname ss (setq i (1- i))))
      (setq ed (entget e))
      (setq typ (cdr (assoc 0 ed)))
      (if (wcmatch typ "*TEXT")
        (write-line (strcat typ "|" (cdr (assoc 1 ed))) f)
      )
      (if (wcmatch typ "DIMENSION")
        (write-line (strcat "DIM|" (rtos (cdr (assoc 42 ed)) 2 0)) f)
      )
    )
  )
  (close f)
  (princ)
)
